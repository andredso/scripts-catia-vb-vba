Attribute VB_Name = "CATIAbasicObjects_01"
Sub CATMain()
    Dim documents1 As Documents
    Set documents1 = CATIA.Documents
    
    MsgBox "The number of documents is " & documents1.Count, vbOKOnly + vbInformation, "Documents Count"
    
    Set documents1 = Nothing
End Sub

Attribute VB_Name = "CATIAbasicObjects_02"
Sub CATMain()
    Dim documents1 As Documents
    Set documents1 = CATIA.Documents
    
    MsgBox "The number of documents is " & documents1.Count, vbOKOnly + vbInformation, "Documents Count"
    
    Dim doc1 As Document
    Set doc1 = documents1.Item(1)
    
    MsgBox doc1.Name, vbOKOnly + vbInformation, "Document Name"
    MsgBox doc1.FullName, vbOKOnly + vbInformation, "Document Name"
    
    
    Set doc1 = Nothing
    Set documents1 = Nothing
End Sub

Attribute VB_Name = "CATIAbasicObjects_03"
Sub CATMain()
    Dim documents1 As Documents
    Set documents1 = CATIA.Documents
    
    MsgBox "The number of documents is " & documents1.Count, vbOKOnly + vbInformation, "Documents Count"
    
    Dim doc1 As Document
    Set doc1 = documents1.Item(1)
    
    For Each doc1 In documents1
        MsgBox doc1.Name, vbOKOnly + vbInformation, "Document Name"
        MsgBox doc1.FullName, vbOKOnly + vbInformation, "Document Name"
    Next
    
    'Dim i As Integer
    'For i = 1 To documents1.Count
    '    Set doc1 = documents1.Item(i)
    '    MsgBox doc1.Name, vbOKOnly + vbInformation, "Document Name"
    '    MsgBox doc1.FullName, vbOKOnly + vbInformation, "Document Name"
    'Next
    'Set doc1 = Nothing
    
    Set doc1 = Nothing
    Set documents1 = Nothing
End Sub

Attribute VB_Name = "CATIAbasicObjects_04"
Sub CATMain()
    Dim documents1 As Documents
    Set documents1 = CATIA.Documents
    
    MsgBox "The number of documents is " & documents1.Count, vbOKOnly + vbInformation, "Documents Count"
    
    Dim doc1 As Document
    Set doc1 = documents1.Item(1)
    
    MsgBox doc1.Name, vbOKOnly + vbInformation, "Document Name"
    MsgBox doc1.FullName, vbOKOnly + vbInformation, "Document Name"
    
    Dim partDoc1 As PartDocument
    Set partDoc1 = doc1
    MsgBox partDoc1.Name, vbOKOnly + vbInformation, "Part Name"
    
    Set doc1 = Nothing
    Set partDoc1 = Nothing
    Set documents1 = Nothing
End Sub

Attribute VB_Name = "CATIAbasicObjects_05"
Sub CATMain()
    Dim documents1 As Documents
    Set documents1 = CATIA.Documents
    
    MsgBox "The number of documents is " & documents1.Count, vbOKOnly + vbInformation, "Documents Count"
    
    Dim doc1 As Document
    Set doc1 = documents1.Item(1)
    
    MsgBox doc1.Name, vbOKOnly + vbInformation, "Document Name"
    MsgBox doc1.FullName, vbOKOnly + vbInformation, "Document Name"
    
    Dim partDoc1 As PartDocument
    Set partDoc1 = doc1
    MsgBox partDoc1.Name, vbOKOnly + vbInformation, "Part Name"
    partDoc1.Close
    
    Set doc1 = Nothing
    Set partDoc1 = Nothing
    Set documents1 = Nothing
End Sub

Attribute VB_Name = "CountPart_01"
Sub CATMain()
    Dim documents1 As Documents
    Set documents1 = CATIA.Documents
    Dim doc1 As Document
    Dim i As Integer
    
    For Each doc1 In documents1
        If InStr(1, doc1.Name, "Part", vbTextCompare) > 0 Then i = i + 1
    Next
    If i > 0 Then
        MsgBox "The number of Part documents is " & i, vbOKOnly + vbInformation, "Part Count"
        For Each doc1 In documents1
            If InStr(1, doc1.Name, "Part", vbTextCompare) > 0 Then
                MsgBox doc1.Name & " in " & doc1.FullName, vbOKOnly + vbInformation, "Part Name"
            End If
        Next
    End If
    Set documents1 = Nothing
End Sub

Attribute VB_Name = "CountPart_02"
Sub CATMain()
    Dim documents1 As Documents
    Set documents1 = CATIA.Documents
    Dim partDoc1 As PartDocument
    Dim i As Integer
    
    For Each partDoc1 In documents1
        i = i + 1
    Next
    If i > 0 Then
        MsgBox "The number of Part documents is " & i, vbOKOnly + vbInformation, "Part Count"
        For Each partDoc1 In documents1
            MsgBox partDoc1.Name & " in " & partDoc1.FullName, vbOKOnly + vbInformation, "Part Name"
        Next
    End If
    Set documents1 = Nothing
End Sub

Attribute VB_Name = "Create_Sketch_01"
Sub CATMain()
'===========================================
' Get the part body
'===========================================
Dim partDocument1 As PartDocument
Set partDocument1 = CATIA.ActiveDocument

Dim part1 As Part
Set part1 = partDocument1.Part

Dim bodies1 As Bodies
Set bodies1 = part1.Bodies

Dim body1 As Body
Set body1 = bodies1.Item("PartBody")

'===============================================
' Add a sketch on the Y-Z Plane
'===============================================
Dim sketches1 As Sketches
Set sketches1 = body1.Sketches

Dim originElements1 As OriginElements
Set originElements1 = part1.OriginElements

Dim reference1 As Reference
Set reference1 = originElements1.PlaneYZ

Dim sketch1 As Sketch
Set sketch1 = sketches1.Add(reference1)

'===============================================
' Set the axis system of the sketch
'===============================================
Dim arrayOfVariantOfDouble1(8)
arrayOfVariantOfDouble1(0) = 0#
arrayOfVariantOfDouble1(1) = 0#
arrayOfVariantOfDouble1(2) = 0#
arrayOfVariantOfDouble1(3) = 0#
arrayOfVariantOfDouble1(4) = 1#
arrayOfVariantOfDouble1(5) = 0#
arrayOfVariantOfDouble1(6) = 0#
arrayOfVariantOfDouble1(7) = 0#
arrayOfVariantOfDouble1(8) = 1#
Set sketch1Variant = sketch1
sketch1Variant.SetAbsoluteAxisData arrayOfVariantOfDouble1

'===============================================
' Creating Sketch Geometry
'===============================================
part1.InWorkObject = sketch1

Dim factory2D1 As Factory2D
Set factory2D1 = sketch1.OpenEdition()

'Dim geometricElements1 As GeometricElements
'Set geometricElements1 = sketch1.GeometricElements
'Dim axis2D1 As Axis2D
'Set axis2D1 = geometricElements1.Item("AbsoluteAxis")
Dim axis2D1 As Axis2D
Set axis2D1 = sketch1.GeometricElements.Item("AbsoluteAxis")

'Dim line2D1 As Line2D
'Set line2D1 = axis2D1.GetItem("HDirection")

'line2D1.ReportName = 1

'Dim line2D2 As Line2D
'Set line2D2 = axis2D1.GetItem("VDirection")

'line2D2.ReportName = 2

Dim point2D1 As Point2D
Set point2D1 = factory2D1.CreatePoint(20#, -40#)

'point2D1.ReportName = 3

Dim point2D2 As Point2D
Set point2D2 = factory2D1.CreatePoint(60#, -70#)

'point2D2.ReportName = 4

Dim line2D3 As Line2D
Set line2D3 = factory2D1.CreateLine(20#, -40#, 60#, -70#)

'line2D3.ReportName = 5

line2D3.StartPoint = point2D1
line2D3.EndPoint = point2D2

sketch1.CloseEdition
part1.InWorkObject = body1
part1.Update
End Sub

Attribute VB_Name = "Messenger"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'Public Message As String
Private strMessage As String
Private iCount As Integer

Property Let Message(MessageIN As String)
    strMessage = MessageIN
    iCount = iCount + 1
End Property

Property Get Message() As String
    Message = strMessage
End Property

Property Get MsgChangeCount() As Integer
    MsgChangeCount = iCount
End Property

Private Sub Class_Initialize()
    iCount = 0
End Sub

Public Sub Capitalize()
    strMessage = UCase(strMessage)
End Sub

Attribute VB_Name = "NavigatePart_01"
Sub CATMain()
    On Error Resume Next
    Dim partDoc1 As PartDocument
    Set partDoc1 = CATIA.ActiveDocument
    
    If Err.Number <> 0 Then
        MsgBox "Active document is not a part document!", vbExclamation + vbOKOnly, "Information"
        Set partDoc1 = Nothing
        End
    End If
    Set partDoc1 = Nothing
End Sub

Attribute VB_Name = "NavigatePart_02"
Sub CATMain()
    On Error Resume Next
    Dim partDoc1 As PartDocument
    Set partDoc1 = CATIA.ActiveDocument

    Dim body1 As Body
    Set body1 = partDoc1.Part.Bodies.Item(1)
    
    Dim shapes1 As Shapes
    Set shapes1 = body1.Shapes
    
    Dim shape1 As Shape
    
    Dim sketchShape As SketchBasedShape
    Dim intCount1 As Integer
    intCount1 = 0
    
    For Each shape1 In shapes1
        Set sketchShape = shape1
        If Err.Number = 0 Then
            intCount1 = intCount1 + 1
        End If
        Set sketchShape = Nothing
        Err.Clear
    Next
    
    MsgBox "Number of sketch based shapes is " & intCount1, vbExclamation + vbOKOnly, "Information"
    
    Set shapes1 = Nothing
    Set body1 = Nothing
    Set partDoc1 = Nothing
End Sub

Attribute VB_Name = "NavigatePart_03"
Sub CATMain()
    On Error Resume Next
    Dim partDoc1 As PartDocument
    Set partDoc1 = CATIA.ActiveDocument

    Dim body1 As Body
    Set body1 = partDoc1.Part.Bodies.Item(1)
    
    Dim shapes1 As Shapes
    Set shapes1 = body1.Shapes
    
    Dim intShapeCount As Integer
    intShapeCount = shapes1.Count
    
    'Dim shape1 As Shape
    Dim sketchShape As SketchBasedShape
    
    Dim intCount1 As Integer
    intCount1 = 0
    
    Dim intI As Integer
    
    For intI = 1 To intShapeCount
        Set sketchShape = shapes1.Item(intI)
        If Err.Number = 0 Then
            intCount1 = intCount1 + 1
        End If
        Set sketchShape = Nothing
        Err.Clear
    Next
    
    MsgBox "Number of sketch based shapes is " & intCount1, vbExclamation + vbOKOnly, "Information"
    
    Set shapes1 = Nothing
    Set body1 = Nothing
    Set partDoc1 = Nothing
End Sub

Attribute VB_Name = "NavigatePart_04"
Sub CATMain()
    On Error Resume Next
    Dim partDoc1 As PartDocument
    Set partDoc1 = CATIA.ActiveDocument

    Dim body1 As Body
    Set body1 = partDoc1.Part.Bodies.Item(1)
    
    Dim shapes1 As Shapes
    Set shapes1 = body1.Shapes
    
    Dim intShapeCount As Integer
    intShapeCount = shapes1.Count
    
    'Dim shape1 As Shape
    Dim sketchShape As SketchBasedShape
    
    Dim intCount1 As Integer
    intCount1 = 0
    
    Dim intI As Integer
    
    For intI = 1 To intShapeCount
        Set sketchShape = shapes1.Item(intI)
        If Err.Number = 0 Then
            intCount1 = intCount1 + 1
        End If
        Set sketchShape = Nothing
        Err.Clear
    Next
    
    MsgBox "Number of sketch based shapes is " & intCount1, vbExclamation + vbOKOnly, "Information"
        
    Set part1 = partDoc1.Part
    
    'Dim hybridShapeFactory1 As HybridShapeFactory
    'Set hybridShapeFactory1 = part1.HybridShapeFactory
        
    'Dim hybridBodies1 As HybridBodies
    'Set hybridBodies1 = part1.HybridBodies
    
    Dim hybridBody1 As HybridBody
    'Set hybridBody1 = hybridBodies1.Item(1)
    Set hybridBody1 = partDoc1.Part.HybridBodies.Item(1)
    
    Dim intGeoCount
    intGeoCount = hybridBody1.HybridShapes.Count
    
    Dim intK, intCount2 As Integer
    Dim datumPlane As HybridShapePlaneExplicit
    intCount2 = 0
        
    For intK = 1 To intGeoCount
        Set datumPlane = hybridBody1.HybridShapes.Item(intK)
        If Err.Number = 0 Then
            intCount2 = intCount2 + 1
        End If
        Set datumPlane = Nothing
        Err.Clear
    Next
    MsgBox "Number of sketch based shapes is: " & intCount1 & vbNewLine _
    & "Number of datum planes is : " & intCount2, vbExclamation + vbOKOnly, "Information"
    
    Set hybridBody1 = Nothing
    'Set hybridBodies1 = Nothing
    'Set hybridShapeFactory1 = Nothing
    Set part1 = Nothing
    Set shapes1 = Nothing
    Set body1 = Nothing
    Set partDoc1 = Nothing
End Sub

Attribute VB_Name = "NavigatePart_05"
Sub CATMain()
    On Error Resume Next
    
    Dim partDoc1 As PartDocument
    Set partDoc1 = CATIA.ActiveDocument

    Dim body1 As Body
    Set body1 = partDoc1.Part.Bodies.Item(1)
    
    Dim shape1 As Shape
    
    Dim sketchShape As SketchBasedShape
    
    Dim intCount1 As Integer
    intCount1 = 0
    
    For Each shape1 In body1.Shapes
        Set sketchShape = shape1
        If Err.Number = 0 Then intCount1 = intCount1 + 1
        Set sketchShape = Nothing
        Err.Clear
    Next
    
    MsgBox "Number of sketch based shapes is " & intCount1, vbExclamation + vbOKOnly, "Information"
        
    Dim part1 As Part
    Set part1 = partDoc1.Part
    
    Dim hybridBody1 As HybridBody
    Set hybridBody1 = partDoc1.Part.HybridBodies.Item(1)
    Dim hybridShape1 As HybridShape
    
    Dim datumPlane As HybridShapePlaneExplicit
    Dim intCount2 As Integer
    intCount2 = 0
        
    For Each hybridShape1 In hybridBody1.HybridShapes
        Set datumPlane = hybridShape1
        If Err.Number = 0 Then intCount2 = intCount2 + 1
        Set datumPlane = Nothing
        Err.Clear
    Next
    MsgBox "Number of sketch based shapes is: " & intCount1 & vbNewLine _
    & "Number of datum planes is : " & intCount2, vbExclamation + vbOKOnly, "Information"
    
    Set hybridBody1 = Nothing
    Set part1 = Nothing
    Set body1 = Nothing
    Set partDoc1 = Nothing
End Sub

Attribute VB_Name = "Show_CreateLine_Form"
Sub CATMain()
    frmCreateLine.Show 'vbModeless
    'form_Create_Sketch_01.Show
End Sub

Attribute VB_Name = "Show_frmSearchInfo_Form"
Sub CATMain()
    frmSearchInfo.Show vbModeless
End Sub

Attribute VB_Name = "TesteOpenDrawing"
Sub CATMain()

Dim documents1 As Documents
Set documents1 = CATIA.Documents

Dim drawingDocument1 As DrawingDocument
Set drawingDocument1 = documents1.Open("C:\en-US\Catia_Estudos\Catparts\drafting ex 3.CATDrawing")

Dim specsAndGeomWindow1 As SpecsAndGeomWindow
Set specsAndGeomWindow1 = CATIA.ActiveWindow

specsAndGeomWindow1.Close

Set drawingDocument1 = CATIA.ActiveDocument

drawingDocument1.Close

End Sub

Attribute VB_Name = "TesteopenProduct"
Sub CATMain()

Dim documents1 As Documents
Set documents1 = CATIA.Documents

Dim productDocument1 As ProductDocument
Set productDocument1 = documents1.Open("C:\en-US\Catia_Estudos\Catparts\montagem_parte_5.CATProduct")

Dim specsAndGeomWindow1 As SpecsAndGeomWindow
Set specsAndGeomWindow1 = CATIA.ActiveWindow

specsAndGeomWindow1.Close

Set productDocument1 = CATIA.ActiveDocument

productDocument1.Close

End Sub

Attribute VB_Name = "UseTheMessenger"
Sub CATMain()
    Dim oMssgr As Messenger
    Set oMssgr = New Messenger
    
    oMssgr.Message = "Hello"
    'oMssgr.Message = "Hello again"
    
    oMssgr.Capitalize
    
    MsgBox oMssgr.Message, vbOKOnly + vbInformation, "Hello Message"
    'MsgBox "Message changed " & oMssgr.MsgChangeCount & " times.", vbOKOnly + vbInformation, "Hello Message"
    
    Set oMssgr = Nothing
End Sub

Attribute VB_Name = "Workshop2_01"
Sub CATMain()
    'Declaration of variables
    Dim intA As Integer
    Dim intB As Integer
    Dim intC As Integer
    
    'Valuate two of the variables
    intA = 2
    intB = 3
    
    'Set the value of the third as a sum of the first two
    intC = intA + intB
    
    'Create a string to be displayed as output.
    'The function Str() converts the integer intC into a String
    Dim strOut As String
    strOut = "The sum is " + Trim(Str(intC)) + "."
    
    'Call a message box to display the output string
    MsgBox strOut
End Sub

Attribute VB_Name = "Workshop2_02"
Sub CATMain()
    Dim intA As Integer
    Dim intB As Integer
    Dim intC As Integer
    intA = 2
    intB = 3
    DisplaySum intA, intB
End Sub

Sub DisplaySum(ByVal int1 As Integer, ByVal int2 As Integer)
    Dim int3 As Integer
    int3 = int1 + int2
    MsgBox "The sum is " + Trim(Str(int3)) + "."
End Sub

Attribute VB_Name = "Workshop2_03"
Sub CATMain()
    Dim intA As Integer
    Dim intB As Integer
    Dim intC As Integer
    intA = 2
    intB = 3
    intC = DisplaySum(intA, intB)
    MsgBox "The sum is " + Trim(Str(intC)) + "."
End Sub

Function DisplaySum(ByVal int1 As Integer, ByVal int2 As Integer) As Integer
    DisplaySum = int1 + int2
End Function

Attribute VB_Name = "Workshop2_04"
Sub CATMain()
    Dim intA(3) As Integer
    Dim intB(3) As Integer
    Dim intC As Integer
    intA(1) = 1
    intA(2) = 2
    intA(3) = 3
    
    intB(1) = 1
    intB(2) = 2
    intB(3) = 3
    
    Dim i As Integer
    For i = 1 To 3
        intC = DisplaySum(intA(i), intB(i))
        MsgBox "The sum of " + Trim(Str(intA(i))) + "+" + Trim(Str(intB(i))) + " is " + Trim(Str(intC)) + "."
    Next i
End Sub

Function DisplaySum(ByVal int1 As Integer, ByVal int2 As Integer) As Integer
    DisplaySum = int1 + int2
End Function

Attribute VB_Name = "frmCreateLine"
Attribute VB_Base = "0{86F11A96-48EF-4FC9-9BCA-779BC25625F4}{D011102B-33B1-4831-BA0E-C50264D03E40}"
Attribute VB_GlobalNameSpace = False
Attribute VB_Creatable = False
Attribute VB_PredeclaredId = True
Attribute VB_Exposed = False
Attribute VB_TemplateDerived = False
Attribute VB_Customizable = False

Private Sub cbCreateLine_Click()
    '===========================================
    ' Get the part body
    '===========================================
    Dim partDocument1 As PartDocument
    Set partDocument1 = CATIA.ActiveDocument
    
    Dim part1 As Part
    Set part1 = partDocument1.Part
    
    Dim bodies1 As Bodies
    Set bodies1 = part1.Bodies
    
    Dim body1 As Body
    Set body1 = bodies1.Item("PartBody")
    
    '===============================================
    ' Add a sketch on the Y-Z Plane
    '===============================================
    Dim sketches1 As Sketches
    Set sketches1 = body1.Sketches
    
    Dim originElements1 As OriginElements
    Set originElements1 = part1.OriginElements
    
    Dim reference1 As Reference
    Set reference1 = originElements1.PlaneYZ
    
    Dim sketch1 As Sketch
    Set sketch1 = sketches1.Add(reference1)
    
    '===============================================
    ' Set the axis system of the sketch
    '===============================================
    Dim arrayOfVariantOfDouble1(8)
    arrayOfVariantOfDouble1(0) = 0#
    arrayOfVariantOfDouble1(1) = 0#
    arrayOfVariantOfDouble1(2) = 0#
    arrayOfVariantOfDouble1(3) = 0#
    arrayOfVariantOfDouble1(4) = 1#
    arrayOfVariantOfDouble1(5) = 0#
    arrayOfVariantOfDouble1(6) = 0#
    arrayOfVariantOfDouble1(7) = 0#
    arrayOfVariantOfDouble1(8) = 1#
    Set sketch1Variant = sketch1
    sketch1Variant.SetAbsoluteAxisData arrayOfVariantOfDouble1
    
    '===============================================
    ' Creating Sketch Geometry
    '===============================================
    part1.InWorkObject = sketch1
    
    Dim factory2D1 As Factory2D
    Set factory2D1 = sketch1.OpenEdition()
    
    'Dim geometricElements1 As GeometricElements
    'Set geometricElements1 = sketch1.GeometricElements
    'Dim axis2D1 As Axis2D
    'Set axis2D1 = geometricElements1.Item("AbsoluteAxis")
    Dim axis2D1 As Axis2D
    Set axis2D1 = sketch1.GeometricElements.Item("AbsoluteAxis")
    
    'Dim line2D1 As Line2D
    'Set line2D1 = axis2D1.GetItem("HDirection")
    
    'line2D1.ReportName = 1
    
    'Dim line2D2 As Line2D
    'Set line2D2 = axis2D1.GetItem("VDirection")
    
    'line2D2.ReportName = 2
    
    Dim point2D1 As Point2D
    Set point2D1 = factory2D1.CreatePoint(tbPointAx.Text, tbPointAy.Text)
    
    'point2D1.ReportName = 3
    
    Dim point2D2 As Point2D
    Set point2D2 = factory2D1.CreatePoint(tbPointBx.Text, tbPointBy.Text)
    
    'point2D2.ReportName = 4
    
    Dim line2D3 As Line2D
    Set line2D3 = factory2D1.CreateLine(tbPointAx.Text, tbPointAy.Text, tbPointBx.Text, tbPointBy.Text)
    
    'line2D3.ReportName = 5
    
    line2D3.StartPoint = point2D1
    line2D3.EndPoint = point2D2
    
    sketch1.CloseEdition
    part1.InWorkObject = body1
    part1.Update
End Sub

Private Sub UserForm_Click()
    'MsgBox "Hello"
    'MsgBox tbPointA.Text
End Sub

Attribute VB_Name = "frmSearchInfo"
Attribute VB_Base = "0{FBEC39AF-9C8F-480E-9F52-49BE4248C748}{973A1245-26FD-4A15-9398-92D87CA061FF}"
Attribute VB_GlobalNameSpace = False
Attribute VB_Creatable = False
Attribute VB_PredeclaredId = True
Attribute VB_Exposed = False
Attribute VB_TemplateDerived = False
Attribute VB_Customizable = False

Private Sub cmbDrivers_Click()
    If (cmbDrivers.ListIndex < 0) Then Exit Sub
    lstFolders.Clear
    lstFiles.Clear
    txtPath.Value = cmbDrivers.Value & "\"
    Preenche_AllListBox cmbDrivers.Value & "\", "all"
End Sub

Private Sub cmdCancel_Click()
    txtPartNumber.Locked = True: txtPartNumber.Value = ""
    txtRevision.Locked = True: txtRevision.Value = ""
    txtDefinition.Locked = True: txtDefinition.Value = ""
    txtNomeclature.Locked = True: txtNomeclature.Value = ""
    txtDescription.Locked = True: txtDescription.Value = ""
    chkCatiaReadOnly.Locked = True: chkCatiaReadOnly.Value = False
    cmdSave.Enabled = False
    cmdCancel.Enabled = False
End Sub

Private Sub cmdEdit_Click()
    If (optCatiaFiles.Value) Or (optProj.Value) Then
        txtPartNumber.Locked = False
        txtRevision.Locked = False
        txtDefinition.Locked = False
        txtNomeclature.Locked = False
        txtDescription.Locked = False
        chkCatiaReadOnly.Locked = False
        cmdEdit.Enabled = False
        cmdSave.Enabled = True
        cmdCancel.Enabled = True
        txtPartNumber.SetFocus
    End If
End Sub

Private Sub cmdExit_Click()
    Unload Me
End Sub

Private Sub cmdSave_Click()
    On Error GoTo ProcErr
    Dim strPathFile$: strPathFile = txtPath.Value & IIf(InStr(1, txtPath.Value, lstFolders.Value, vbTextCompare) = 0, lstFolders.Value & "\", "") & lstFiles.Value
    Dim RootProduct As Product
    Dim drawingDocument1 As DrawingDocument
    Dim doc1 As Document
    Dim sFSO As New FileSystemObject: Set sFSO = CreateObject("Scripting.FileSystemObject")
    Dim Fl: Set Fl = sFSO.GetFile(strPathFile)
    If (chkCatiaReadOnly.Value) Then
        Fl.Attributes = vbReadOnly
    Else
        Fl.Attributes = vbNormal
    End If
    Set Fl = Nothing
    Set sFSO = Nothing
    If (InStr(1, lstFiles.Value, "CATProduct", vbTextCompare) > 0) Then
        'Set doc1 = CATIA.Documents.Read(strPathFile)
        If (InStr(1, CATIA.ActiveDocument.Name, "CATProduct", vbTextCompare) = 0) Then
            Set RootProduct = CATIA.Documents.Open(strPathFile).Product
        Else
            Set RootProduct = CATIA.ActiveDocument.Product
        End If
        Set doc1 = CATIA.ActiveDocument
        RootProduct.PartNumber = txtPartNumber.Value
        RootProduct.Revision = txtRevision.Value
        RootProduct.Definition = txtDefinition.Value
        RootProduct.Nomenclature = txtNomeclature.Value
        RootProduct.DescriptionRef = txtDescription.Value
        doc1.Save
        Set doc1 = Nothing
        Set RootProduct = Nothing
    ElseIf (InStr(1, lstFiles.Value, "CATPart", vbTextCompare) > 0) Then
        Set RootProduct = CATIA.ActiveDocument.Product
        If (RootProduct.Products.Count > 0) Then
            Set doc1 = CATIA.Documents.Open(strPathFile)
        Else
            Set doc1 = CATIA.ActiveDocument
        End If
        Set RootProduct = CATIA.ActiveDocument.Product
        RootProduct.PartNumber = txtPartNumber.Value
        RootProduct.Revision = txtRevision.Value
        RootProduct.Definition = txtDefinition.Value
        RootProduct.Nomenclature = txtNomeclature.Value
        RootProduct.DescriptionRef = txtDescription.Value
        doc1.Save
        If (RootProduct.Products.Count > 0) Then doc1.Close
        Set doc1 = Nothing
        Set RootProduct = Nothing
    ElseIf (InStr(1, lstFiles.Value, "CATDrawing", vbTextCompare) > 0) Then
        Set drawingDocument1 = CATIA.Documents.Open(strPathFile)
        drawingDocument1.Name = txtNomeclature.Value
        drawingDocument1.Save: drawingDocument1.Close
        Set drawingDocument1 = Nothing
    End If
    txtPartNumber.Locked = True
    txtRevision.Locked = True
    txtDefinition.Locked = True
    txtNomeclature.Locked = True
    txtDescription.Locked = True
    chkCatiaReadOnly.Locked = True
    cmdEdit.Enabled = True
    cmdSave.Enabled = False
    cmdCancel.Enabled = False
ProcErr:
    If (Err <> 0) Then
        MsgBox Err & vbCr & Err.Description
        Resume Next
    End If
End Sub

Private Sub lstFiles_Click()
    On Error GoTo ProcErr
    If (lstFiles.ListCount < 1) Then Exit Sub
    Dim strPathFile$: strPathFile = txtPath.Value & IIf(InStr(1, txtPath.Value, lstFolders.Value, vbTextCompare) = 0, lstFolders.Value & "\", "") & lstFiles.Value
    Dim sFSO As New FileSystemObject: Set sFSO = CreateObject("Scripting.FileSystemObject")
    Dim Fl: Set Fl = sFSO.GetFile(strPathFile)
    Dim Drv As Drive
    txtNameSelFile.Value = Fl.Name
    txtTypeSelFile.Value = Fl.Type
    txtDateCreatedSelFile.Value = Format(Fl.DateCreated, "General Date")
    txtDateLastAccessedSelFile.Value = Format(Fl.DateLastAccessed, "General Date")
    txtDateLastModifiedSelFile.Value = Format(Fl.DateLastModified, "General Date")
    Limpa_FileAttrCheckBoxes
    Atualiza_FileAttrCheckBoxes Fl.Attributes
    If (InStr(1, lstFiles.Value, "CATProduct", vbTextCompare) > 0) Then Info_CatiaFile strPathFile, "CATProduct"
    If (InStr(1, lstFiles.Value, "CATPart", vbTextCompare) > 0) Then Info_CatiaFile strPathFile, "CATPart"
    If (InStr(1, lstFiles.Value, "CATDrawing", vbTextCompare) > 0) Then Info_CatiaFile strPathFile, "CATDrawing"
    If (optCatiaFiles.Value) Or (optProj.Value) Then cmdEdit.Enabled = True
    Set Fl = Nothing
    Set sFSO = Nothing
ProcErr:
    If (Err <> 0) Then
        MsgBox Err & vbCr & Err.Description
        Resume Next
    End If
End Sub

Private Sub lstFolders_Click()
    If (lstFolders.ListCount < 1) Or (lstFolders.Value = "<---") Then Exit Sub
    If (optProj.Value) Then optAllFiles.Value = True
    lstFiles.Clear
    Preenche_AllListBox txtPath.Value & lstFolders.Value, "files"
    cmdEdit.Enabled = False
End Sub

Private Sub lstFolders_DblClick(ByVal Cancel As MSForms.ReturnBoolean)
    If (optProj.Value) Then optAllFiles.Value = True
    If (lstFolders.Value = "<---") Then
        lstFolders.Clear: lstFiles.Clear
        txtPath.Value = Pasta_Anterior(txtPath.Value)
        Preenche_AllListBox txtPath.Value, "all"
    Else
        txtPath.Value = txtPath.Value & lstFolders.Value & "\"
        lstFolders.Clear: lstFiles.Clear
        Preenche_AllListBox txtPath.Value, "<---"
    End If
    cmdEdit.Enabled = False
End Sub

Private Sub optAllFiles_Click()
    If (lstFolders.ListCount < 1) Or (lstFolders.Value = "<---") Then Exit Sub
    lstFiles.Clear
    Preenche_AllListBox txtPath.Value & lstFolders.Value, "files"
    cmdEdit.Enabled = False
End Sub

Private Sub optCatiaFiles_Click()
    If (lstFolders.ListCount < 1) Or (lstFolders.Value = "<---") Then Exit Sub
    lstFiles.Clear
    Preenche_AllListBox txtPath.Value & lstFolders.Value, "files"
End Sub

Private Sub optProj_Click()
    Load_CatiaFilesProject
End Sub

Private Sub UserForm_Initialize()
    Preenche_DriversComboBox
    cmbDrivers.ListIndex = 0
    optAllFiles.Value = True
    optCatiaFiles.Value = False
    optProj.Value = False
End Sub

Private Function Pasta_Anterior(ByVal strPath$) As String
    Dim intI%
    For intI = InStr(Len(strPath) - 1, Trim(strPath), "\", vbTextCompare) - 1 To 1 Step -1
        If (Mid(strPath, intI, 1) = "\") Then
            Pasta_Anterior = Mid(strPath, 1, intI)
            Exit For
        End If
    Next intI
End Function

Private Sub Preenche_AllListBox(ByVal strPath$, ByVal strTypeListBox$)
    On Error GoTo ProcErr
    Dim Sfd, f1, Fls
    Dim sFSO As New FileSystemObject: Set sFSO = CreateObject("Scripting.FileSystemObject")
    Dim Drv As Drive
    Dim Fd: Set Fd = sFSO.GetFolder(strPath)
    Dim intJ%, intQtdeBarras%
    If (strTypeListBox <> "files") Then
        intJ = 0: intQtdeBarras = 0
        For intJ = 1 To Len(txtPath.Value)
            If (Mid(txtPath.Value, intJ, 1) = "\") Then intQtdeBarras = intQtdeBarras + 1
        Next intJ
        If (intQtdeBarras > 1) Then lstFolders.AddItem "<---"
    End If
    If (strTypeListBox = "<---") Then
        For Each Sfd In Fd.SubFolders
            lstFolders.AddItem Sfd.Name
        Next
        For Each Fls In Fd.Files
            If (optCatiaFiles.Value) And (InStr(1, CStr(Fls.Type), "CATIA", vbTextCompare) > 0) Then lstFiles.AddItem Fls.Name
            If (optAllFiles.Value) Then lstFiles.AddItem Fls.Name
        Next Fls
    End If
    If (strTypeListBox = "all") Or (strTypeListBox = "folders") Then
        For Each Sfd In Fd.SubFolders
            If (InStr(1, Sfd.Name, ".", vbTextCompare) = 0) Then lstFolders.AddItem Sfd.Name
        Next
    End If
    If (strTypeListBox = "all") Or (strTypeListBox = "files") Then
        For Each Fls In Fd.Files
            If (optCatiaFiles.Value) And (InStr(1, CStr(Fls.Type), "CATIA", vbTextCompare) > 0) Then lstFiles.AddItem Fls.Name
            If (optAllFiles.Value) Then lstFiles.AddItem Fls.Name
        Next Fls
    End If
    txtNameSelFile.Value = ""
    txtTypeSelFile.Value = ""
    txtDateCreatedSelFile.Value = ""
    txtDateLastAccessedSelFile.Value = ""
    txtDateLastModifiedSelFile.Value = ""
    txtPartNumber.Value = ""
    txtRevision.Value = ""
    txtDefinition.Value = ""
    txtNomeclature.Value = ""
    txtDescription.Value = ""
    Limpa_FileAttrCheckBoxes
    Set Fd = Nothing
    Set sFSO = Nothing
ProcErr:
    If (Err.Number = 70) Then
        MsgBox "Sem permissão de acesso!", vbOKOnly + vbCritical, "Acesso Restrito!"
        Set Fd = Nothing
        Set sFSO = Nothing
        Exit Sub
    ElseIf (Err <> 0) Then
        MsgBox Err & vbCr & Err.Description
        Resume Next
    End If
End Sub

Private Sub Preenche_DriversComboBox()
    On Error GoTo ProcErr
    Dim sFSO As New FileSystemObject: Set sFSO = CreateObject("Scripting.FileSystemObject")
    Dim Drv As Drive
    If (sFSO.drives.Count > 0) Then
        For Each Drv In sFSO.drives
            cmbDrivers.AddItem Drv.DriveLetter & ":"
        Next
    End If
    Set sFSO = Nothing
ProcErr:
    If (Err <> 0) Then
        MsgBox Err & vbCr & Err.Description
        Resume Next
    End If
End Sub

Private Sub Limpa_FileAttrCheckBoxes()
    chkNormal.Value = False
    chkReadOnly.Value = False
    chkHidden.Value = False
    chkSystem.Value = False
    chkArchive.Value = False
    chkCatiaReadOnly.Value = False
End Sub

Private Sub Atualiza_FileAttrCheckBoxes(ByVal lngFileAttr&)
    On Error GoTo ProcErr
    'Dim FileAttr& : FileAttr = GetAttr(strPath) : lblResult.Caption = "&&H" & Hex$(result)
    'Dim FileAttr As FileAttribute : FileAttr = GetAttr(strPath)
    If (lngFileAttr) And (vbNormal) Then
        chkNormal.Value = True
    Else
        chkNormal.Value = False
    End If
    If (lngFileAttr) And (vbReadOnly) Then
        chkReadOnly.Value = True
    Else
        chkReadOnly.Value = False
    End If
    If (lngFileAttr) And (vbHidden) Then
        chkHidden.Value = True
    Else
        chkHidden.Value = False
    End If
    If (lngFileAttr) And (vbSystem) Then
        chkSystem.Value = True
    Else
        chkSystem.Value = False
    End If
    'If (lngFileAttr) And (vbDirectory) Then
    '    chkDirectory.Value = True
    'Else
    '    chkDirectory.Value = False
    'End If
    If (lngFileAttr) And (vbArchive) Then
        chkArchive.Value = True
    Else
        chkArchive.Value = False
    End If
ProcErr:
    If (Err <> 0) Then
        MsgBox Err & vbCr & Err.Description
        Resume Next
    End If
End Sub

Private Sub Info_CatiaFile(ByVal strPath$, ByVal strTypeFileCatia$)
    On Error GoTo ProcErr
    Dim RootProduct As Product
    Dim doc1 As Document
    Dim drawingDocument1 As DrawingDocument
    txtPartNumber.Value = ""
    txtRevision.Value = ""
    txtDefinition.Value = ""
    txtNomeclature.Value = ""
    txtDescription.Value = ""
    chkCatiaReadOnly.Value = False
    If (strTypeFileCatia <> "CATDrawing") Then
        Set RootProduct = CATIA.Documents.Read(strPath).Product
        Set doc1 = CATIA.Documents.Read(strPath)
        txtPartNumber.Value = RootProduct.PartNumber
        txtRevision.Value = RootProduct.Revision
        txtDefinition.Value = RootProduct.Definition
        txtNomeclature.Value = RootProduct.Nomenclature
        txtDescription.Value = RootProduct.DescriptionRef
        chkCatiaReadOnly.Value = doc1.ReadOnly
        Set doc1 = Nothing
        Set RootProduct = Nothing
    Else
        Set drawingDocument1 = CATIA.Documents.Read(strPath)
        txtNomeclature.Value = drawingDocument1.Name
        chkCatiaReadOnly.Value = drawingDocument1.ReadOnly
        Set drawingDocument1 = Nothing
    End If
    'Dim documents1 As Documents
    'Set documents1 = CATIA.Documents
    'Select Case strTypeFileCatia
    '    Case Is = "CATProduct"
    '        FileToOpen = "e:\users\psr\Parts\ThisIsANicePart.CATPart"
    '        Set doc1 = documents1.Read(strPath)
    '        Dim productDocument1 As ProductDocument
    '        Set productDocument1 = documents1.Open(strPath)
    '    Case Is = "CATPart"
    '        Dim partDocument1 As PartDocument
    '        Set partDocument1 = documents1.Read(strPath)
    '    Case Is = "CATDrawing"
    '        Dim drawingDocument1 As DrawingDocument
    '        Set drawingDocument1 = documents1.Read(strPath)
    'End Select
ProcErr:
    If (Err <> 0) Then
        MsgBox Err & vbCr & Err.Description
        Resume Next
    End If
End Sub

Private Sub Load_CatiaFilesProject()
    On Error GoTo ProcErr
    If (CATIA.ActiveDocument.Path = "") Then
        optAllFiles.Value = True
        Exit Sub
    End If
    Dim RootProduct As Product: Set RootProduct = CATIA.ActiveDocument.Product
    Dim EngineChildren As Products
    Dim RootProductChildren As Product
    Dim doc1 As Document
    lstFolders.Clear
    lstFiles.Clear
    txtPath.Value = CATIA.ActiveDocument.Path & "\"
    txtPartNumber.Value = ""
    txtRevision.Value = ""
    txtDefinition.Value = ""
    txtNomeclature.Value = ""
    txtDescription.Value = ""
    chkCatiaReadOnly.Value = False
    Preenche_AllListBox txtPath.Value, "<---"
    lstFiles.Clear: lstFiles.AddItem CATIA.ActiveDocument.Name
    If (CATIA.Documents.Count > 1) Then
        Set EngineChildren = RootProduct.Products
        For Each doc1 In CATIA.Documents
            For Each RootProductChildren In EngineChildren
                If (InStr(1, doc1.Name, RootProductChildren.PartNumber, vbTextCompare) > 0) Then
                    lstFiles.AddItem doc1.Name
                    Exit For
                End If
            Next RootProductChildren
        Next doc1
        Set EngineChildren = Nothing
    End If
    Set doc1 = Nothing
    Set RootProduct = Nothing
ProcErr:
    If (Err.Number = -2147467259) Then
        Resume Next
    ElseIf (Err.Number = -2147418113) Then
        Exit Sub
    ElseIf (Err.Number <> 0) Then
        MsgBox Err & vbCr & Err.Description
        Resume Next
    End If
End Sub

'Private Function ListaArquivosESubPastas(ByVal path$) As String
'  On Error GoTo ProcErr
'  Dim Fsfd, Fd, Sfd, f1, Fls, Itn$
'  If path = "" Then Exit Function
'  Set Fsfd = CreateObject("Scripting.FileSystemObject")
'  Set Fd = Fsfd.GetFolder(path$)
'  Do While Fd.path <> ".."
'    For Each Fls In Fd.Files
'      'SysCmd acSysCmdSetStatus, Fd.path$ & "\" & Fls.name
'      Debug.Print Fd.path$ & "\" & Fls.Name
'    Next Fls
'    For Each Sfd In Fd.SubFolders
'      f1 = f1 + 1
'      Itn = Sfd.Name
'      Debug.Print f1 & " de " & Fd.SubFolders.Count & " ( " & Fd.path$ & "\" & Itn & " )"
'      ListaArquivosESubPastas Fd.path$ & "\" & Itn & "\"
'    Next
'    GoSub Proc_Sai
'  Loop
'Proc_Sai:
'  Set Fsfd = Nothing: Set Fd = Nothing:  Set Sfd = Nothing: Set f1 = Nothing
'  Exit Function
'ProcErr:
'  If Err = 76 Then Resume Proc_Sai
'  MsgBox Err & vbCr & Err.Description
'  Resume Next
'End Function

'Sub GetFileInfo(sFile As String)
'    Dim sFileAttrib As Long
'    Dim sFileInfo As String
'    sFileAttrib = GetAttr(sFile)
'    ' Get Attibutes and fill attribute string
'    If (sFileAttrib And vbReadOnly) = vbReadOnly Then
'        sFileInfo = sFileInfo & "Read Only"
'    End If
'    If (sFileAttrib And vbArchive) = vbArchive Then
'        sFileInfo = sFileInfo & " Archive"
'    End If
'    If (sFileAttrib And vbNormal) = vbNormal Then
'        sFileInfo = sFileInfo & " Normal"
'    End If
'    If (sFileAttrib And vbSystem) = vbSystem Then
'        sFileInfo = sFileInfo & " System"
'    End If
'    If (sFileAttrib And vbHidden) = vbHidden Then
'        sFileInfo = sFileInfo & " Hidden"
'    End If
'    If (sFileAttrib And vbDirectory) = vbDirectory Then
'        sFileInfo = sFileInfo & " Directory"
'    End If
'    MsgBox sFile & " has the following properties: " & sFileInfo
'End Sub
'https://www.youtube.com/channel/UC8vNNsorbQ1gfRVqxW9xEqw/videos

Attribute VB_Name = "teste"
Sub CATMain()
    Dim documents1 As Documents
    Set documents1 = CATIA.Documents
    Dim RootProduct As Product
    Set RootProduct = documents1.Item(1).Product
    If documents1.Count > 1 Then
        Dim EngineChildren As Products
        Set EngineChildren = RootProduct.Products
        Dim RootProductChildren As Product
        For Each RootProductChildren In EngineChildren
            Exit For
        Next
    Else
        
    End If

    'For Each doc1 In documents1
    '    If InStr(1, doc1.Name, "CATProduct", vbTextCompare) > 0 Then
    '        Set RootProduct = doc1.Product
    '    End If
    '    If InStr(1, doc1.Name, "CATPart", vbTextCompare) > 0 Then
    '        'Dim partDoc1 As Part
    '        'Set partDoc1 = doc1.Part
    '        Set RootProduct = doc1.Product
    '    End If
    'Next
    'https://www.youtube.com/watch?v=XDgHkS8BsZ4
    'https://www.youtube.com/watch?v=RzdQMipB4Hg
    
    'Print doc1.FullName
    'C:\en-US\Catia_Estudos\Catparts\montagem_parte_5.CATProduct
    
    'Print doc1.Name
    'montagem_parte_5.CATProduct
    
    'Print doc1.Path
    'C:\en-US\Catia_Estudos\Catparts
    
    'Print doc1.ReadOnly
    'False
    
    'Dim i As Integer
    
    Set RootProduct = Nothing
    Set EngineChildren = Nothing
    Set documents1 = Nothing
End Sub

Attribute VB_Name = "testeopenPart"
Sub CATMain()

Dim documents1 As Documents
Set documents1 = CATIA.Documents

Dim partDocument1 As PartDocument
Set partDocument1 = documents1.Open("C:\en-US\Catia_Estudos\Catparts\Borracha.CATPart")

Dim specsAndGeomWindow1 As SpecsAndGeomWindow
Set specsAndGeomWindow1 = CATIA.ActiveWindow

specsAndGeomWindow1.Close

Set partDocument1 = CATIA.ActiveDocument

partDocument1.Close

End Sub
